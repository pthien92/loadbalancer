module loadbalancer {
    yang-version 1;
    namespace "urn:opendaylight:params:xml:ns:yang:loadbalancer";
    prefix "loadbalancer";

    revision "2015-01-05" {
        description "Initial revision of loadbalancer model";
    }
}
